# aeb_requirements

## REQ-01: Speed ≥ 30 km/h AND obstacle ≤ 20 m AND sensor valid → BRAKE (Functional)
Speed ≥ 30 km/h AND obstacle ≤ 20 m AND sensor valid → BRAKE
Expected output: BRAKE

## REQ-02: Speed < 30 km/h → NO_ACTION (regardless of obstacle) (Functional)
Speed < 30 km/h → NO_ACTION (regardless of obstacle)
Expected output: NO_ACTION

## REQ-03: Sensor age ≥ 200 ms → FAULT (Functional)
Sensor age ≥ 200 ms → FAULT
Expected output: FAULT

## REQ-04: In FAULT, sensor healthy for 1 s → return to NORMAL (Functional)
In FAULT, sensor healthy for 1 s → return to NORMAL
Expected output: NORMAL

## REQ-05: Speed outside [0, 250] km/h → FAULT (invalid input) (Functional)
Speed outside [0, 250] km/h → FAULT (invalid input)
Expected output: FAULT
